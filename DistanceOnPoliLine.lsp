; Скрипт для вимірювання довжини сегмента полілінії між двома точками,
; розташування яких вказується користувачем (можна використовувати 'Уявний перетин').
; Команда для запуску: DPL

(vl-load-com) ; Переконатись, що функції ActiveX/VLA завантажені

(defun c:DPL ( / *error* old_osmode old_cmdecho ent obj pt1_raw pt2_raw pt1 pt2 dist1 dist2 seg_length )

  ; Функція обробки помилок
  (defun *error* ( msg )
    ; Важливо відновити OSMODE, якщо він був змінений, але в цій версії ми його не змінюємо примусово.
    ; Залишаємо відновлення на випадок майбутніх модифікацій або якщо користувач скасує під час роботи іншої команди, що змінила OSMODE.
    (if old_osmode (setvar "OSMODE" old_osmode))
    (if old_cmdecho (setvar "CMDECHO" old_cmdecho)) ; Відновити старі налаштування відображення команд
    (cond
      ((not msg)) ; Вихід без помилки (наприклад, натискання Esc)
      ((wcmatch (strcase msg) "*BREAK,*CANCEL*,*EXIT*")) ; Нормальний вихід користувача
      (T (princ (strcat "\nПомилка: " msg))) ; Показати повідомлення про помилку
    )
    (princ) ; Тихий вихід
  )

  ; Зберегти поточні налаштування
  (setq old_osmode (getvar "OSMODE")) ; Зберігаємо поточні прив'язки користувача
  (setq old_cmdecho (getvar "CMDECHO"))
  (setvar "CMDECHO" 0) ; Вимкнути відображення команд для чистоти

  ; --- Вибір полілінії ---
  (setq ent nil)
  (while (not ent)
    (setq ent (entsel "\nВиберіть полілінію, вздовж якої буде вимірювання: "))
    (if ent
      (progn
        (setq obj (vlax-ename->vla-object (car ent)))
        (if (not (wcmatch (vla-get-ObjectName obj) "*Polyline")) ; Перевірка, чи це полілінія
          (progn
            (prompt "\nОбраний об'єкт не є полілінією. Спробуйте ще раз.")
            (setq ent nil) ; Скинути вибір, щоб цикл продовжився
          )
        )
      )
      (prompt "\nОб'єкт не вибрано.")
    )
  )

  (if ent ; Продовжувати тільки якщо полілінію вибрано
    (progn
      ; --- Вибір РОЗТАШУВАННЯ першої точки ---
      ; НЕ змінюємо OSMODE примусово - користувач може використовувати свої активні прив'язки
      (prompt "\nУвімкніть потрібні об'єктні прив'язки (напр. 'Уявний перетин').")
      (setq pt1_raw (getpoint "\nВкажіть РОЗТАШУВАННЯ першої точки сегмента: "))
      (if pt1_raw
        (progn
          ; Знаходимо НАЙБЛИЖЧУ точку НА ПОЛІЛІНІЇ до вказаного розташування
          (setq pt1 (vlax-curve-getClosestPointTo obj pt1_raw))
          ; Отримуємо відстань вздовж полілінії до цієї точки
          (setq dist1 (vlax-curve-getDistAtPoint obj pt1))

          ; --- Вибір РОЗТАШУВАННЯ другої точки ---
          (setq pt2_raw (getpoint pt1_raw "\nВкажіть РОЗТАШУВАННЯ другої точки сегмента: ")) ; Використовуємо pt1_raw для гумової нитки
          (if pt2_raw
            (progn
              ; Знаходимо НАЙБЛИЖЧУ точку НА ПОЛІЛІНІЇ до вказаного розташування
              (setq pt2 (vlax-curve-getClosestPointTo obj pt2_raw))
              ; Отримуємо відстань вздовж полілінії до цієї точки
              (setq dist2 (vlax-curve-getDistAtPoint obj pt2))

              ; --- Обчислення та виведення результату ---
              (setq seg_length (abs (- dist2 dist1))) ; Довжина - це різниця відстаней по модулю

              (alert (strcat "Довжина сегмента полілінії між найближчими точками: " (rtos seg_length 2 2)))
              (prompt (strcat "\nДовжина сегмента полілінії між найближчими точками до вказаних: " (rtos seg_length 2 2)))
            )
            (prompt "\nРозташування другої точки не вказано.")
          )
        )
        (prompt "\nРозташування першої точки не вказано.")
      )
    )
  )

  ; Відновлюємо налаштування (хоча ми активно змінювали тільки CMDECHO)
  (setvar "OSMODE" old_osmode)
  (setvar "CMDECHO" old_cmdecho)
  (princ) ; Тихий вихід з функції
)

(princ "\nСкрипт DPL (з підтримкою уявних перетинів) завантажено. Введіть DPL для запуску.")
(princ)
